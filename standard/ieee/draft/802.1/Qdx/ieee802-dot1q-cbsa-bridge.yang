module ieee802-dot1q-cbsa-bridge {
  namespace "urn:ieee:std:802.1Q:yang:ieee802-dot1q-cbsa-bridge";
  prefix cbsa-bridge;

  import ietf-interfaces {
    prefix if;
  }
  import ieee802-dot1q-cbsa {
    prefix cbsa;
  }
  import ieee802-dot1q-bridge {
    prefix dot1q;
  }

  organization
    "IEEE 802.1 Working Group";
  contact
    "WG-URL: http://www.ieee802.org/1/
    WG-EMail: stds-802-1-L@ieee.org

    Contact: IEEE 802.1 Working Group Chair
    Postal: C/O IEEE 802.1 Working Group
    IEEE Standards Association
    445 Hoes Lane
    Piscataway, NJ 08854
    USA

    E-mail: stds-802-1-chairs@ieee.org";
  description
    "This module provides for management of IEEE Std 802.1Q Bridges
    that support the credit-based shaper algorithm.

    Copyright (C) IEEE (2024).

    This version of this YANG module is part of IEEE Std 802.1Q; see the
    standard itself for full legal notices.";

  revision 2024-03-22 {
    description
      "Published as part of IEEE Std 802.1Qdx-2024.
	  
      The following reference statement identifies each referenced IEEE
      Standard as updated by applicable amendments.";
    reference
      "IEEE Std 802.1Q Bridges and Bridged Networks:
      IEEE Std 802.1Q-2022, IEEE Std 802.1Qcz-2023, IEEE Std 802.1Qcw-2023,
      IEEE Std 802.1Qcj-2023, IEEE Std 802.1Qdx-2024.";
  }

  feature credit-based-shaper-algorithm {
    description
      "Credit-based shaper algorithm supported.";
    reference
      "8.6.8.2 of IEEE Std 802.1Q.";
  }

  augment "/if:interfaces/if:interface/dot1q:bridge-port" {
    if-feature "credit-based-shaper-algorithm";
    description
      "Augment dot1q:bridge-port with credit-based shaper algorithm 
      configuration.";
    uses cbsa:cbsa-parameters;
  }
}
